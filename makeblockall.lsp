; (defun HL:insertBoundingBox (allblocklist insertb ent / ab bb)  
;   (if allblocklist
;       (progn
;         (setq ab (car allblocklist))
;         (setq bb (car ab))
;         (if (HL:isBoundingBoxCross bb insertb)
;             (if (= (type ent) 'ENAME)
;               (cons (cons (HL:mergeBoundingBox bb insertb) (cons ent (cdr ab))) (cdr allblocklist))
;               (cons (cons (HL:mergeBoundingBox bb insertb) (append ent (cdr ab))) (cdr allblocklist))              
;             )
;             (cons ab (HL:insertBoundingBox (cdr allblocklist) insertb ent))
;         )
;       )
;       (if (= (type ent) 'ENAME)
;          (list (cons insertb (list ent)))
;          (list (cons insertb ent))
;       )
;   )
; )
;
;flattenListでlistに変換するのでlistにlistを結合している
(defun HL:insertBoundingBox (allblocklist insertb ent / ab bb)  
  (if allblocklist
      (progn
        (setq ab (car allblocklist))
        (setq bb (car ab))
        (if (HL:isBoundingBoxCross bb insertb)
            (cons (cons (HL:mergeBoundingBox bb insertb) (cons ent (cdr ab))) (cdr allblocklist))                        
            (cons ab (HL:insertBoundingBox (cdr allblocklist) insertb ent))
        )
      )
      (if (= (type ent) 'ENAME)
         (list (cons insertb (list ent)))
         (list (cons insertb ent))
      )
  )
)

(defun HL:getBoundingBoxPlus ( ent eps / ret minpt maxpt)    
    (setq ret (HL:getBoundingBox ent))
    (setq minpt (car ret))
    (setq maxpt (cdr ret))
    (cons (list (- (car minpt) eps) (- (cadr minpt) eps)) (list (+ (car maxpt) eps) (+ (cadr maxpt) eps)))
)
(defun c:makeblockall ( / selectset ent allblocklist tmp myset point bname OldOSNAP lengthblocklist nextlengthblocklist nblocklist blist eps neps tmplist HL:flattenList)
  (if (not HL:ISLOADUTILITY_LSP)
    (progn 
      (alert "you must load utility.lsp\n")
      (quit)
    )
  )  
  (HL:A_start)
  (HL:randinit)  
  (while (null selectset)
    (setq selectset (HL:getNameList (ssget '((0 . "ARC,CIRCLE,LINE,LWPOLYLINE,SPLINE,ELLIPSE,INSERT")))))
  )
  (setq eps 0.5)
  (setq neps nil)
  (setq neps (getreal "merge length<0.5>:"))
  (if neps
     (setq eps neps)
  )
  (foreach ent selectset    
    (setq allblocklist (HL:insertBoundingBox allblocklist (HL:getBoundingBoxPlus ent eps) ent))
  )
  
  (setq lengthblocklist (length allblocklist))
  (setq nextlengthblocklist 0)
  (while (/= lengthblocklist nextlengthblocklist)
      (progn
      (setq lengthblocklist (length allblocklist))      
      (setq nblocklist nil)       
      (foreach blist allblocklist
         (setq nblocklist (HL:insertBoundingBox nblocklist (car blist) (cdr blist)))
      )
      (setq allblocklist nblocklist)
      (setq nextlengthblocklist (length allblocklist))
      )
  )
  (setq tmplist nil)
  (defun HL:flattenList (l / lt)
      (if (= (type l) 'LIST)
          (foreach lt l
            (HL:flattenList lt)
          )
          (setq tmplist (cons l tmplist))
      )
  )    
  (foreach tmp allblocklist
    (setq tmplist nil)
    (HL:flattenList (cdr tmp))
    (setq myset (HL:toSet tmplist))    
    (setq point (caar tmp))
    (setq point (list (car point) (cadr point) 0.0))    
    (setq point (trans point 0 1))      
    (setq bname (strcat "makeblockall" (itoa (HL:randrange 0 1000000))))
    (while (tblsearch "block" bname)
      (setq bname (strcat "makeblockall" (itoa (HL:randrange 0 1000000))))
    )
    (setq oldOSNAP (getvar "OSMODE"))
    (setvar "OSMODE" 0)
    (command-s "._-block" bname point myset "")
    (command-s "._-insert" bname point 1 1 0)
    (setvar "OSMODE" oldOSNAP)
  )  
  (print (length allblocklist))
  (HL:A_end)
)
