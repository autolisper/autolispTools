(defun HL:alllayerName ( / l name)
  (setq name T)
  (while name
    (setq name (HL:A_dxf 2 (tblnext "LAYER" (not name))))
    (if name
      (setq ret (cons name ret))
    )
  )
  ret
)
(defun HL:isvaliddata (datas / )
  (= (length datas) 2)
)
(defun HL:extrudePoly (obj height taper / curves region solidObj)
  (setq curves (vlax-make-safearray vlax-vbObject '(0 . 0)))
  (vlax-safearray-put-element curves 0 obj)
  (setq region (vla-AddRegion (HL:modelspace) curves))
  (setq region (vlax-safearray-get-element (vlax-variant-value region) 0))  
  (setq solidObj (vla-AddExtrudedSolid (HL:modelSpace) region height taper))  
  (vla-delete region)
  solidObj
)
(defun HL:copyMove (ename point / point1 point2)
  (setq copyobj (vla-copy (vlax-ename->vla-object ename)))
  (setq point1 (vlax-3d-point '(0 0 0))
          point2 (vlax-3d-point point))                
    ;; Move the circle
  (vla-Move copyobj point1 point2)    
  copyobj
)
(defun HL:makesolid (nameList name datas trayheight / height taper ename ret copyobj point1 point2)  
  (setq height (atof (car datas)))
  (setq taper (HL:neg (angtof (cadr datas))))  
  (setq nameList (vl-remove-if-not '(lambda (x) (= name (HL:A_dxf 8 x))) nameList))    
  ;is close check  
  (foreach ename nameList
    (setq copyobj (HL:copyMove ename (list 0 0 height)))    
    (setq ret (cons (HL:extrudePoly copyobj (- trayheight height) taper) ret))
    (vla-delete copyobj)        
  )
  ret
)
(defun HL:picktype (objtype message / ret)  
  (while (not ret)
    (setq ret (car (entsel message)))
    (princ "\n")
    (if (not (= (HL:A_dxf 0 ret) objtype))
        (setq ret nil)
    )
  )
  ret
)
(defun c:3dtaper ( / layers name datas nameList trayheight allsolid baseobj basepoly copyobj unionset )
  (setq layers (HL:alllayerName))  
  (setq nameList (HL:getNameList (ssget '((0 . "LWPOLYLINE")))))    
  (setq trayheight (getreal "trayheight:"))
  (setq basepoly (HL:picktype "LWPOLYLINE" "basepoly:"))
  (setq copyobj (HL:copyMove basepoly '(0 0 -10)))
  (setq baseobj (HL:extrudePoly copyobj (+ trayheight 10) 0.0))
  (vla-delete copyobj)
  (foreach name layers    
    (setq datas (HL:splitWith name "@"))    
    (if (HL:isvaliddata datas) 
      (setq allsolid (append allsolid (HL:makesolid nameList name datas trayheight)))
    )
  )
  (command-s "._union" (HL:toSet (mapcar 'vlax-vla-object->ename allsolid)) "")
  (setq unionset (ssget "p"))
  (command-s "._subtract" (HL:toSet (list (vlax-vla-object->ename baseobj))) "" unionset "")
  (princ)
)
